;;; Native AutoCAD entity operations. All coordinates are micrometres in WCS.

(defun qlay:escape (s / i c n out)
  (setq i 1 out "")
  (repeat (strlen s)
    (setq c (substr s i 1) n (ascii c) i (1+ i))
    (setq out (strcat out (cond ((= c "\"") "\\\"") ((= c "\\") "\\\\")
      ((= n 10) "\\n") ((= n 13) "\\r") ((= n 9) "\\t") (T c))))) out)
(defun qlay:jnum (x / s)
  (setq s (if (= (type x) 'INT) (itoa x) (rtos x 2 16)))
  (if (= (substr s 1 1) ".") (setq s (strcat "0" s)))
  (if (= (substr s 1 2) "-.") (setq s (strcat "-0" (substr s 2))))
  (if (= (substr s (strlen s) 1) ".") (setq s (strcat s "0"))) s)
(defun qlay:join (items sep / out)
  (setq out "") (foreach v items (setq out (strcat out (if (= out "") "" sep) v))) out)
(defun qlay:json (v)
  (cond ((null v) "[]") ((= v T) "true") ((= (type v) 'STR) (strcat "\"" (qlay:escape v) "\""))
    ((numberp v) (qlay:jnum v)) ((listp v) (strcat "[" (qlay:join (mapcar 'qlay:json v) ",") "]"))
    (T (strcat "\"" (qlay:escape (vl-princ-to-string v)) "\""))))
(defun qlay:object (pairs)
  (strcat "{" (qlay:join (mapcar '(lambda (p) (strcat (qlay:json (car p)) ":" (qlay:json (cdr p)))) pairs) ",") "}"))

(defun qlay:layer (name color / e d)
  (if (not (tblsearch "LAYER" name))
    (entmake (list '(0 . "LAYER") '(100 . "AcDbSymbolTableRecord") '(100 . "AcDbLayerTableRecord")
      (cons 2 name) '(70 . 0) (cons 62 color) '(6 . "Continuous")))) name)
(defun qlay:visible (name visible / e d c)
  (setq e (tblobjname "LAYER" name) d (entget e) c (abs (cdr (assoc 62 d))))
  (entmod (subst (cons 62 (if visible c (- c))) (assoc 62 d) d)) name)
(defun qlay:color (name color / e d)
  (setq e (tblobjname "LAYER" name) d (entget e))
  (entmod (subst (cons 62 color) (assoc 62 d) d)) name)
(defun qlay:make (data / e)
  (setq e (entmakex data))
  (if e (cdr (assoc 5 (entget e))) (vl-exit-with-error "Native entity creation failed")))
(defun qlay:polygon (layer hull holes / data loops index loop)
  (qlay:layer layer 7)
  (setq loops (cons hull holes) index 0
    data (list '(0 . "HATCH") '(100 . "AcDbEntity") (cons 8 layer) '(100 . "AcDbHatch")
      '(10 0.0 0.0 0.0) '(210 0.0 0.0 1.0) '(2 . "SOLID") '(70 . 1) '(71 . 0) (cons 91 (length loops))))
  (foreach loop loops
    (setq data (append data (list (cons 92 (if (= index 0) 3 2)) '(72 . 0) '(73 . 1) (cons 93 (length loop)))))
    (foreach pt loop (setq data (append data (list (cons 10 pt)))))
    (setq data (append data (list '(97 . 0))) index (1+ index)))
  (qlay:make (append data (list '(75 . 0) '(76 . 1) '(98 . 0)))))
(defun qlay:path (layer points width closed / data)
  (qlay:layer layer 7)
  (setq data (list '(0 . "LWPOLYLINE") '(100 . "AcDbEntity") (cons 8 layer) '(100 . "AcDbPolyline")
    (cons 90 (length points)) (cons 70 (if closed 1 0)) (cons 43 width)))
  (foreach pt points (setq data (append data (list (cons 10 pt))))) (qlay:make data))
(defun qlay:info (/ ss e d i layers result count)
  (setq layers nil count 0)
  (setq d (tblnext "LAYER" T))
  (while d (setq layers (cons (cdr (assoc 2 d)) layers) d (tblnext "LAYER")))
  (setq ss (ssget "_X")) (if ss (setq count (sslength ss)))
  (qlay:object (list (cons "name" (getvar "DWGNAME")) (cons "units" (getvar "INSUNITS"))
    (cons "entity_count" count) (cons "layers" (reverse layers)))))
(defun qlay:attach-image (path layer origin uvec vvec / oldfile oldecho previous e d image-dict image-name old-def result)
  (qlay:layer layer 7)
  ;; A packaged IMAGEDEF may retain its original symbol name while its file
  ;; path becomes relative. Reattaching the original file then prompts for a
  ;; replacement symbol. Rename that dictionary key first; existing IMAGEs
  ;; reference the same object ID and retain their content and transforms.
  (setq image-dict (cdr (assoc -1 (dictsearch (namedobjdict) "ACAD_IMAGE_DICT")))
    image-name (vl-filename-base path))
  (if (and image-dict (setq old-def (dictsearch image-dict image-name)))
    (if (not (dictrename image-dict image-name (strcat image-name "_QLAY_" (cdr (assoc 5 old-def)))))
      (vl-exit-with-error "Cannot allocate a unique image definition name")))
  (setq oldfile (getvar "FILEDIA") oldecho (getvar "CMDECHO") previous (entlast))
  (setvar "FILEDIA" 0) (setvar "CMDECHO" 0)
  (setq result (vl-catch-all-apply '(lambda () (command-s "_.-IMAGE" "_Attach" path '(0.0 0.0) 1.0 0.0)) nil))
  (setvar "FILEDIA" oldfile) (setvar "CMDECHO" oldecho)
  (if (vl-catch-all-error-p result) (vl-exit-with-error (vl-catch-all-error-message result)))
  (setq e (entlast))
  (if (or (not e) (eq e previous)) (vl-exit-with-error "Image attachment did not create an entity"))
  (setq d (entget e))
  (if (/= (cdr (assoc 0 d)) "IMAGE") (vl-exit-with-error "Image attachment did not create an IMAGE"))
  (setq d (subst (cons 8 layer) (assoc 8 d) d)
    d (subst (cons 10 (append origin '(0.0))) (assoc 10 d) d)
    d (subst (cons 11 (append uvec '(0.0))) (assoc 11 d) d)
    d (subst (cons 12 (append vvec '(0.0))) (assoc 12 d) d))
  (entmod d) (entupd e) (cdr (assoc 5 d)))
(defun qlay:images (/ ss i d def out)
  (setq ss (ssget "_X" '((0 . "IMAGE"))) out nil i 0)
  (if ss (repeat (sslength ss)
    (setq d (entget (ssname ss i)) def (entget (cdr (assoc 340 d))) i (1+ i))
    (setq out (cons (qlay:object (list (cons "handle" (cdr (assoc 5 d)))
      (cons "path" (cdr (assoc 1 def))) (cons "origin" (cdr (assoc 10 d)))
      (cons "uvec" (cdr (assoc 11 d))) (cons "vvec" (cdr (assoc 12 d))))) out))))
  (strcat "[" (qlay:join (reverse out) ",") "]"))
"qlay-runtime-ready"
